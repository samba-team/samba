-- $Id$

GSS-API DEFINITIONS ::= BEGIN

IMPORTS HEIM_ANY_SET FROM heim;

GSSAPIContextToken ::= [APPLICATION 0] IMPLICIT SEQUENCE {
	thisMech OBJECT IDENTIFIER,
	innerContextToken HEIM_ANY_SET
}

END
